module interface_config {
  namespace "http://com/example/interface_config";
  prefix interface_config;

  import ietf-inet-types {
    prefix inet;
  }
  import tailf-ncs {
    prefix ncs;
  }

  list interface_config {
    key name;

    uses ncs:service-data;
    ncs:servicepoint "interface_config";

    leaf name {
      type string;
    }

    // Reference to devices
    leaf-list device {
      type leafref {
        path "/ncs:devices/ncs:device/ncs:name";
      }
    }

    container interface {
       list GigabitEthernet {
          key id;

          leaf id {
            type string {
              pattern "^[0-9]+/[0-9]+/[0-9]+/[0-9]+$";
            }
          }

          container ipv4 {
             list address {
                key "ip";
                leaf ip {
                   type inet:ip-address;
                }
                leaf mask {
                   type inet:ipv4-address;
                }
            }
         }
       }
     }
  }
}
